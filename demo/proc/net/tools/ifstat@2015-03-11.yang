module if {
  namespace "urn:ietf:params:xml:ns:yang:dummy";
  prefix if;

  import ietf-yang-types {
    prefix yang;
  }

  typedef interface-state-ref {
    type leafref {
      path "/if:interfaces-state/if:interface/if:name";
    }
    description
      "This type is used by data models that need to reference
       the operationally present interfaces.";
  }

  identity interface-type {
    description
      "Base identity from which specific interface types are
       derived.";
  }

  feature if-mib {
    description
      "This feature indicates that the device implements
       the IF-MIB.";
    reference
      "RFC 2863: The Interfaces Group MIB";
  }

  container interfaces-state {
    config false;
    description
      "Data nodes for the operational state of interfaces.";

    list interface {
      key "name";

      leaf name {
        type string;
        }

      leaf type {
        type identityref {
          base interface-type;
        }
        mandatory true;
        }

      leaf admin-status {
        if-feature if-mib;
        type enumeration {
          enum up {
            value 1;
            description
              "Ready to pass packets.";
          }
          enum down {
            value 2;
            description
              "Not ready to pass packets and not in some test mode.";
          }

          enum testing {
            value 3;
            description
              "In some test mode.";
          }
        }
        mandatory true;
        }

      leaf oper-status {
        type enumeration {
          enum up {
            value 1;
            description
              "Ready to pass packets.";
          }
          enum down {
            value 2;
            description
              "The interface does not pass any packets.";
          }
          enum testing {
            value 3;
            description
              "In some test mode.  No operational packets can
               be passed.";
          }
          enum unknown {
            value 4;
            description
              "Status cannot be determined for some reason.";
          }
          enum dormant {
            value 5;
            description
              "Waiting for some external event.";
          }
          enum not-present {
            value 6;
            description
              "Some component (typically hardware) is missing.";
          }
          enum lower-layer-down {
            value 7;
            description
              "Down due to state of lower-layer interface(s).";
          }
        }
        mandatory true;
        }

      leaf if-index {
        if-feature if-mib;
        type int32 {
          range "1..2147483647";
        }
        mandatory true;
      }

      leaf phys-address {
        type yang:phys-address;
      }

      leaf-list higher-layer-if {
        type interface-state-ref;
      }

      leaf-list lower-layer-if {
        type interface-state-ref;
        description
          "A list of references to interfaces layered underneath this
           interface.";
        reference
          "RFC 2863: The Interfaces Group MIB - ifStackTable";
      }

      leaf speed {
        type yang:gauge64;
        units "bits/second";
      }

      container statistics {

        leaf discontinuity-time {
          type yang:date-and-time;
          mandatory true;
        }

        leaf in-octets {
          type yang:counter64;
        }

        leaf in-unicast-pkts {
          type yang:counter64;
        }

        leaf in-broadcast-pkts {
          type yang:counter64;
        }

        leaf in-multicast-pkts {
          type yang:counter64;
        }

        leaf in-discards {
          type yang:counter32;
        }

        leaf in-errors {
          type yang:counter32;
        }

        leaf in-unknown-protos {
          type yang:counter32;
        }

        leaf out-octets {
          type yang:counter64;
        }

        leaf out-unicast-pkts {
          type yang:counter64;
        }

        leaf out-broadcast-pkts {
          type yang:counter64;
        }


        leaf out-multicast-pkts {
          type yang:counter64;
        }

        leaf out-discards {
          type yang:counter32;
        }

        leaf out-errors {
          type yang:counter32;
        }
      }
    }
  }

}
